# FMUDATA

## #1: Constants (Container)

### FMUDATA-96: CTR_TK_LO_LVL_DELAY (Functional)
CTR_TK_LO_LVL_DELAY = 180 sec

### FMUDATA-171: FUEL_BALANCE_COMPLETE_DELAY (Functional)
FUEL_BALANCE_COMPLETE_DELAY = 10 sec

### FMUDATA-170: FUEL_BALANCE_COMPLETE_TH (Functional)
FUEL_BALANCE_COMPLETE_TH = 75 kg

### FMUDATA-1: FAULT_DETECT_CONFIRM_DELAY (Functional)
FAULT_DETECT_CONFIRM_DELAY = 0.5 sec

### FMUDATA-97: FLIGHT_PHASE_TAKEOFF (Functional)
FLIGHT_PHASE_TAKEOFF = 3

### FMUDATA-2: FUEL_LEVEL_MIN (Functional)
FUEL_LEVEL_MIN = 0 gal

### FMUDATA-3: FUEL_LEVEL_MAX (Functional)
FUEL_LEVEL_MAX = 1000 gal

### FMUDATA-4: FUEL_TANK_TEMP_OVHT_RESET_DELAY (Functional)
FUEL_TANK_TEMP_OVHT_RESET_DELAY = 2 sec

### FMUDATA-5: FUEL_TANK_TEMP_OVHT_SET_DELAY (Functional)
FUEL_TANK_TEMP_OVHT_SET_DELAY = 3 sec

### FMUDATA-6: FUEL_TANK_TEMP_OVHT_TH_RESET (Functional)
FUEL_TANK_TEMP_OVHT_TH_RESET = 125 DegC

### FMUDATA-7: FUEL_TANK_TEMP_OVHT_TH_SET (Functional)
FUEL_TANK_TEMP_OVHT_TH_SET = 130 DegC

### FMUDATA-8: IN_ENGINE_TEMP_ICD_MAX (Functional)
IN_ENGINE_TEMP_ICD_MAX = 240 DegC

### FMUDATA-9: IN_ENGINE_TEMP_ICD_MIN (Functional)
IN_ENGINE_TEMP_ICD_MIN = -60 DegC

### FMUDATA-10: IN_CTR_TK_FUEL_LEVEL_ICD_MAX (Functional)
12000 kg

### FMUDATA-11: IN_CTR_TK_FUEL_LEVEL_ICD_MIN (Functional)
IN_ENGINE_TEMP_ICD_MIN = 0 kg

### FMUDATA-12: IN_FUEL_TANK_TEMP_ICD_MAX (Functional)
IN_FUEL_TANK_TEMP_ICD_MAX = 150 DegC

### FMUDATA-13: IN_FUEL_TANK_TEMP_ICD_MIN (Functional)
IN_FUEL_TANK_TEMP_ICD_MIN = -30 DegC

### FMUDATA-14: IN_FUEL_TANK_TEMP_MIN (Functional)
IN_FUEL_TANK_TEMP_MIN = 0 DegC

### FMUDATA-15: IN_GROUND_SPEED_ICD_MAX (Functional)
IN_GROUND_SPEED_ICD_MAX = 121 kts

### FMUDATA-16: IN_GROUND_SPEED_ICD_MIN (Functional)
IN_GROUND_SPEED_ICD_MIN = 0 kts

### FMUDATA-17: IN_RECORDED_SPEED_ICD_MAX (Functional)
IN_RECORDED_SPEED_ICD_MAX = 250 kts

### FMUDATA-18: IN_RECORDED_SPEED_ICD_MIN (Functional)
IN_RECORDED_SPEED_ICD_MIN = 5 kts

### FMUDATA-19: IN_FLIGHT_TH (Functional)
IN_FLIGHT_TH = 100 kts

### FMUDATA-72: ISM_FAULT_CONFIRM_DELAY (Functional)
ISM_FAULT_CONFIRM_DELAY = 10 sec

### FMUDATA-20: LEAK_DETECTION_DELAY (Functional)
LEAK_DETECTION_DELAY = 5 sec

### FMUDATA-21: LEAK_DETECTION_DELAY2 (Functional)
LEAK_DETECTION_DELAY2 = 15 sec

### FMUDATA-22: LEAK_DETECT_THRESHOLD (Functional)
LEAK_DETECT_THRESHOLD = 5 gal

### FMUDATA-23: OVERSPEED_FAULT_DELAY (Functional)
OVERSPEED_FAULT_DELAY = 5 sec

### FMUDATA-24: STABLE_FLIGHT_DELAY (Functional)
STABLE_FLIGHT_DELAY = 5 sec

### FMUDATA-78: IN_FLIGHT_PHASE_ICD_MIN (Functional)
IN_FLIGHT_PHASE_ICD_MIN = 1

### FMUDATA-79: IN_FLIGHT_PHASE_ICD_MAX (Functional)
IN_FLIGHT_PHASE_ICD_MAX = 8

### FMUDATA-163: WING_TK_FUEL_LEVEL_ICD_MIN (Functional)
WING_TK_FUEL_LEVEL_ICD_MIN = 0 kg

### FMUDATA-164: WING_TK_FUEL_LEVEL_ICD_MAX (Functional)
WING_TK_FUEL_LEVEL_ICD_MAX = 2500 kg

### FMUDATA-201: FUEL_IMALANCE_DISPLAY_TH (Functional)
FUEL_IMALANCE_DISPLAY_TH = 1000 kg

### FMUDATA-202: FUEL_IMBALANCE_DISPLAY_DELAY (Functional)
FUEL_IMBALANCE_DISPLAY_DELAY = 5 sec

### FMUDATA-227: LP_MFLD_PRESSURE_ICD_MAX (Functional)
LP_MFLD_PRESSURE_ICD_MAX = 200 psi

### FMUDATA-226: LP_MFLD_PRESSURE_ICD_MIN (Functional)
LP_MFLD_PRESSURE_ICD_MIN = 0 psi

### FMUDATA-236: LP_LOW_PRESSURE_TH (Functional)
LP_LOW_PRESSURE_TH = 10 psi

### FMUDATA-237: LP_LOW_PRESSURE_RESET_TH (Functional)
LP_LOW_PRESSURE_RESET_TH = 20 psi

### FMUDATA-238: LP_LOW_PRESSURE_DELAY (Functional)
LP_LOW_PRESSURE_DELAY = 1 sec

### FMUDATA-290: FUEL_LEVEL_ICD_MIN (Functional)
FUEL_LEVEL_ICD_MIN = 0 kg

### FMUDATA-291: FUEL_LEVEL_ICD_MAX (Functional)
FUEL_LEVEL_ICD_MAX = 17000 kg

## #44: External Signals (Container)

### FMUDATA-25: IN_BRAKE_SENSOR (Functional)

### FMUDATA-26: IN_BRAKE_SENSOR_ACTIVE (Functional)

### FMUDATA-98: IN_CTR_TK_LOW_LEVEL (Functional)

### FMUDATA-99: IN_CTR_TK_LOW_LEVEL_ACTIVE (Functional)

### FMUDATA-80: IN_CTR_TK_MAN_SWITCH (Functional)

### FMUDATA-81: IN_CTR_TK_MAN_SWITCH_ACTIVE (Functional)

### FMUDATA-84: IN_CTR_TK_PUMP_1_SWITCH (Functional)

### FMUDATA-85: IN_CTR_TK_PUMP_1_SWITCH_ACTIVE (Functional)

### FMUDATA-86: IN_CTR_TK_PUMP_2_SWITCH (Functional)

### FMUDATA-87: IN_CTR_TK_PUMP_2_SWITCH_ACTIVE (Functional)

### FMUDATA-27: IN_ENGINE_TEMP (Functional)

### FMUDATA-28: IN_ENGINE_TEMP_ACTIVE (Functional)

### FMUDATA-67: IN_FAULT_IGNORE (Functional)

### FMUDATA-68: IN_FAULT_IGNORE_ACTIVE (Functional)

### FMUDATA-74: IN_FLIGHT_PHASE (Functional)

### FMUDATA-75: IN_FLIGHT_PHASE_ACTIVE (Functional)

### FMUDATA-152: IN_FUEL_BALANCE_PB (Functional)

### FMUDATA-153: IN_FUEL_BALANCE_PB_ACTIVE (Functional)

### FMUDATA-29: IN_CTR_TK_FUEL_LEVEL (Functional)

### FMUDATA-30: IN_CTR_TK_FUEL_LEVEL_ACTIVE (Functional)

### FMUDATA-31: IN_FUEL_TANK_TEMP (Functional)

### FMUDATA-32: IN_FUEL_TANK_TEMP_ACTIVE (Functional)

### FMUDATA-33: IN_GROUND_SPEED (Functional)

### FMUDATA-34: IN_GROUND_SPEED_ACTIVE (Functional)

### FMUDATA-161: IN_L_TK_FUEL_LEVEL (Functional)

### FMUDATA-162: IN_L_TK_FUEL_LEVEL_ACTIVE (Functional)

### FMUDATA-104: IN_L_TK_HI_LEVEL (Functional)

### FMUDATA-105: IN_L_TK_HI_LEVEL_ACTIVE (Functional)

### FMUDATA-100: IN_L_TK_LOW_LEVEL (Functional)

### FMUDATA-101: IN_L_TK_LOW_LEVEL_ACTIVE (Functional)

### FMUDATA-118: IN_L_TK_PUMP_1_SWITCH (Functional)

### FMUDATA-119: IN_L_TK_PUMP_1_SWITCH_ACTIVE (Functional)

### FMUDATA-120: IN_L_TK_PUMP_2_SWITCH (Functional)

### FMUDATA-121: IN_L_TK_PUMP_2_SWITCH_ACTIVE (Functional)

### FMUDATA-35: IN_ON_GROUND (Functional)

### FMUDATA-36: IN_ON_GROUND_ACTIVE (Functional)

### FMUDATA-37: IN_PBIT_STATUS (Functional)

### FMUDATA-38: IN_PBIT_STATUS_ACTIVE (Functional)

### FMUDATA-39: IN_RECORDED_SPEED (Functional)

### FMUDATA-40: IN_RECORDED_SPEED_ACTIVE (Functional)

### FMUDATA-165: IN_R_TK_FUEL_LEVEL (Functional)

### FMUDATA-166: IN_R_TK_FUEL_LEVEL_ACITVE (Functional)

### FMUDATA-102: IN_R_TK_LOW_LEVEL (Functional)

### FMUDATA-103: IN_R_TK_LOW_LEVEL_ACTIVE (Functional)

### FMUDATA-106: IN_R_TK_HI_LEVEL (Functional)

### FMUDATA-107: IN_R_TK_HI_LEVEL_ACTIVE (Functional)

### FMUDATA-122: IN_R_TK_PUMP_1_SWITCH (Functional)

### FMUDATA-123: IN_R_TK_PUMP_1_SWITCH_ACTIVE (Functional)

### FMUDATA-124: IN_R_TK_PUMP_2_SWITCH (Functional)

### FMUDATA-125: IN_R_TK_PUMP_2_SWITCH_ACTIVE (Functional)

### FMUDATA-140: IN_XFEED_VALVE_SWITCH (Functional)

### FMUDATA-141: IN_XFEED_VALVE_SWITCH_ACTIVE (Functional)

### FMUDATA-148: IN_XFEED_VALVE_FULLY_CLOSED (Functional)

### FMUDATA-149: IN_XFEED_VALVE_FULLY_CLOSED_ACTIVE (Functional)

### FMUDATA-150: IN_XFEED_VALVE_FULLY_OPEN (Functional)

### FMUDATA-151: IN_XFEED_VALVE_FULLY_OPEN_ACTIVE (Functional)

### FMUDATA-243: IN_L_REFUEL_VALVE_FULLY_CLOSED (Functional)

### FMUDATA-244: IN_L_REFUEL_VALVE_FULLY_CLOSED_ACTIVE (Functional)

### FMUDATA-245: IN_L_REFUEL_VALVE_FULLY_OPEN (Functional)

### FMUDATA-246: IN_L_REFUEL_VALVE_FULLY_OPEN_ACTIVE (Functional)

### FMUDATA-247: IN_R_REFUEL_VALVE_FULLY_CLOSED (Functional)

### FMUDATA-248: IN_R_REFUEL_VALVE_FULLY_CLOSED_ACTIVE (Functional)

### FMUDATA-249: IN_R_REFUEL_VALVE_FULLY_OPEN (Functional)

### FMUDATA-250: IN_R_REFUEL_VALVE_FULLY_OPEN_ACTIVE (Functional)

### FMUDATA-251: IN_C_REFUEL_VALVE_FULLY_CLOSED (Functional)

### FMUDATA-252: IN_C_REFUEL_VALVE_FULLY_CLOSED_ACTIVE (Functional)

### FMUDATA-253: IN_C_REFUEL_VALVE_FULLY_OPEN (Functional)

### FMUDATA-254: IN_C_REFUEL_VALVE_FULLY_OPEN_ACTIVE (Functional)

### FMUDATA-271: IN_L_TK_REFUEL_SW (Functional)

### FMUDATA-272: IN_R_TK_REFUEL_SW (Functional)

### FMUDATA-273: IN_C_TK_REFUEL_SW (Functional)

### FMUDATA-274: IN_TK_REFUEL_SW_ACTIVE (Functional)

### FMUDATA-275: IN_FUEL_XFER_MODE (Functional)

### FMUDATA-276: IN_FUEL_XFER_MODE_ACTIVE (Functional)

### FMUDATA-279: IN_DEFUEL_VALVE_FULLY_OPEN (Functional)

### FMUDATA-280: IN_DEFUEL_VALVE_FULLY_CLOSED (Functional)

### FMUDATA-281: IN_DEFUEL_VALVE_ACTIVE (Functional)

### FMUDATA-288: IN_DESIRED_FUEL_LEVEL (Functional)

### FMUDATA-289: IN_DESIRED_FUEL_LEVEL_ACTIVE (Functional)

### FMUDATA-292: IN_CTR_TK_HI_LEVEL (Functional)

### FMUDATA-293: IN_CTR_TK_HI_LEVEL_ACTIVE (Functional)

### FMUDATA-172: IN_ENG1_RUNNING (Functional)

### FMUDATA-173: IN_ENG1_RUNNING_ACTIVE (Functional)

### FMUDATA-174: IN_ENG2_RUNNING (Functional)

### FMUDATA-175: IN_ENG2_RUNNING_ACTIVE (Functional)

### FMUDATA-187: IN_FUEL_BALANCE_VALVE_L_FULLY_OPEN (Functional)

### FMUDATA-188: IN_FUEL_BALANCE_VALVE_L_FULLY_OPEN_ACTIVE (Functional)

### FMUDATA-189: IN_FUEL_BALANCE_VALVE_R_FULLY_OPEN (Functional)

### FMUDATA-190: IN_FUEL_BALANCE_VALVE_R_FULLY_OPEN_ACTIVE (Functional)

### FMUDATA-191: IN_FUEL_BALANCE_VALVE_L_FULLY_CLOSED (Functional)

### FMUDATA-192: IN_FUEL_BALANCE_VALVE_L_FULLY_CLOSED_ACTIVE (Functional)

### FMUDATA-193: IN_FUEL_BALANCE_VALVE_R_FULLY_CLOSED (Functional)

### FMUDATA-194: IN_FUEL_BALANCE_VALVE_R_FULLY_CLOSED_ACTIVE (Functional)

### FMUDATA-206: IN_APU_RUNNING (Functional)

### FMUDATA-207: IN_APU_RUNNING_ACTIVE (Functional)

### FMUDATA-208: IN_APU_MASTER_SWITCH (Functional)

### FMUDATA-209: IN_APU_MASTER_SWITCH_ACTIVE (Functional)

### FMUDATA-212: IN_APU_FIRE (Functional)

### FMUDATA-213: IN_APU_FIRE_ACTIVE (Functional)

### FMUDATA-216: IN_APU_LP_VALVE_FULLY_OPEN (Functional)

### FMUDATA-217: IN_APU_LP_VALVE_FULLY_OPEN_ACTIVE (Functional)

### FMUDATA-220: IN_APU_LP_VALVE_FULLY_CLOSED (Functional)

### FMUDATA-221: IN_APU_LP_VALVE_FULLY_CLOSED_ACTIVE (Functional)

### FMUDATA-228: IN_L_LP_MFLD_PRESSURE (Functional)

### FMUDATA-229: IN_L_LP_MFLD_PRESSURE_ACTIVE (Functional)

### FMUDATA-234: IN_R_LP_MFLD_PRESSURE (Functional)

### FMUDATA-235: IN_R_LP_MFLD_PRESSURE_ACTIVE (Functional)

## #47: Internal Signals (Container)

### FMUDATA-58: AC_NO_GO (Functional)

### FMUDATA-69: AUTO_FAULT_DETECT_ENABLED (Functional)

### FMUDATA-61: BRAKE_SENSOR_STATUS (Functional)

### FMUDATA-62: BRAKE_SENSOR_STATUS_VALID (Functional)

### FMUDATA-108: CTR_TK_LOW_LEVEL (Functional)

### FMUDATA-109: CTR_TK_LOW_LEVEL_VALID (Functional)

### FMUDATA-82: CTR_TK_MAN_SWITCH (Functional)

### FMUDATA-83: CTR_TK_MAN_SWITCH_VALID (Functional)

### FMUDATA-94: CTR_TK_PUMP_1_AUTO_STOP (Functional)

### FMUDATA-92: CTR_TK_PUMP_1_ENABLE (Functional)

### FMUDATA-88: CTR_TK_PUMP_1_SWITCH (Functional)

### FMUDATA-89: CTR_TK_PUMP_1_SWITCH_VALID (Functional)

### FMUDATA-95: CTR_TK_PUMP_2_AUTO_STOP (Functional)

### FMUDATA-93: CTR_TK_PUMP_2_ENABLE (Functional)

### FMUDATA-90: CTR_TK_PUMP_2_SWITCH (Functional)

### FMUDATA-91: CTR_TK_PUMP_2_SWITCH_VALID (Functional)

### FMUDATA-65: ENGINE_TEMP_S1 (Functional)

### FMUDATA-66: ENGINE_TEMP_VALID_S1 (Functional)

### FMUDATA-52: FAULT_DETECT_ENABLED (Functional)

### FMUDATA-70: FAULT_IGNORE (Functional)

### FMUDATA-71: FAULT_IGNORE_VALID (Functional)

### FMUDATA-76: FLIGHT_PHASE (Functional)

### FMUDATA-77: FLIGHT_PHASE_VALID (Functional)

### FMUDATA-156: FUEL_BALANCE_ENABLE (Functional)

### FMUDATA-157: FUEL_BALANCE_ENABLE_RESET (Functional)

### FMUDATA-154: FUEL_BALANCE_PB (Functional)

### FMUDATA-155: FUEL_BALANCE_PB_VALID (Functional)

### FMUDATA-47: CTR_TK_FUEL_LEVEL (Functional)

### FMUDATA-48: CTR_TK_FUEL_LEVEL_VALID (Functional)

### FMUDATA-53: FUEL_LEVEL_LEAK_DETECT_VALUE_1 (Functional)

### FMUDATA-54: FUEL_LEVEL_LEAK_DETECT_VALUE_1_VALID (Functional)

### FMUDATA-55: FUEL_LEVEL_LEAK_DETECT_VALUE_2 (Functional)

### FMUDATA-56: FUEL_LEVEL_LEAK_DETECT_VALUE_2_VALID (Functional)

### FMUDATA-57: FUEL_LEVEL_LEAK (Functional)

### FMUDATA-49: FUEL_LEVEL_XDCR_FAULT (Functional)

### FMUDATA-41: FUEL_TANK_TEMP (Functional)

### FMUDATA-42: FUEL_TANK_TEMP_VALID (Functional)

### FMUDATA-43: FUEL_TANK_OVHT_LATCHED (Functional)

### FMUDATA-44: FUEL_TANK_OVHT_LATCHED_RESET (Functional)

### FMUDATA-158: FUEL_WING_TK_LEVEL_DIFF (Functional)

### FMUDATA-59: GROUND_SPEED (Functional)

### FMUDATA-60: GROUND_SPEED_VALID (Functional)

### FMUDATA-73: ISM_FAULT (Functional)

### FMUDATA-159: L_TK_FUEL_LEVEL (Functional)

### FMUDATA-160: L_TK_FUEL_LEVEL_VALID (Functional)

### FMUDATA-112: L_TK_LOW_LEVEL (Functional)

### FMUDATA-113: L_TK_LOW_LEVEL_VALID (Functional)

### FMUDATA-116: L_TK_HI_LEVEL (Functional)

### FMUDATA-117: L_TK_HI_LEVEL_VALID (Functional)

### FMUDATA-134: L_TK_PUMP_1_ENABLE (Functional)

### FMUDATA-126: L_TK_PUMP_1_SWITCH (Functional)

### FMUDATA-127: L_TK_PUMP_1_SWITCH_VALID (Functional)

### FMUDATA-135: L_TK_PUMP_2_ENABLE (Functional)

### FMUDATA-128: L_TK_PUMP_2_SWITCH (Functional)

### FMUDATA-129: L_TK_PUMP_2_SWITCH_VALID (Functional)

### FMUDATA-63: ON_GROUND (Functional)

### FMUDATA-64: ON_GROUND_VALID (Functional)

### FMUDATA-45: PBIT_STATUS (Functional)

### FMUDATA-46: PBIT_STATUS_VALID (Functional)

### FMUDATA-50: RECORDED_SPEED (Functional)

### FMUDATA-51: RECORDED_SPEED_VALID (Functional)

### FMUDATA-167: R_TK_FUEL_LEVEL (Functional)

### FMUDATA-168: R_TK_FUEL_LEVEL_VALID (Functional)

### FMUDATA-110: R_TK_LOW_LEVEL (Functional)

### FMUDATA-111: R_TK_LOW_LEVEL_VALID (Functional)

### FMUDATA-114: R_TK_HI_LEVEL (Functional)

### FMUDATA-115: R_TK_HI_LEVEL_VALID (Functional)

### FMUDATA-136: R_TK_PUMP_1_ENABLE (Functional)

### FMUDATA-130: R_TK_PUMP_1_SWITCH (Functional)

### FMUDATA-131: R_TK_PUMP_1_SWITCH_VALID (Functional)

### FMUDATA-137: R_TK_PUMP_2_ENABLE (Functional)

### FMUDATA-132: R_TK_PUMP_2_SWITCH (Functional)

### FMUDATA-133: R_TK_PUMP_2_SWITCH_VALID (Functional)

### FMUDATA-143: XFEED_VALVE_CLOSE_CMD (Functional)

### FMUDATA-144: XFEED_VALVE_FULLY_CLOSED (Functional)

### FMUDATA-145: XFEED_VALVE_FULLY_CLOSED_VALID (Functional)

### FMUDATA-146: XFEED_VALVE_FULLY_OPEN (Functional)

### FMUDATA-147: XFEED_VALVE_FULLY_OPEN_VALID (Functional)

### FMUDATA-142: XFEED_VALVE_OPEN_CMD (Functional)

### FMUDATA-138: XFEED_VALVE_SWITCH (Functional)

### FMUDATA-139: XFEED_VALVE_SWITCH_VALID (Functional)

### FMUDATA-169: FUEL_BALANCE_INHIBIT (Functional)

### FMUDATA-176: ENG1_RUNNING (Functional)

### FMUDATA-177: ENG1_RUNNING_VALID (Functional)

### FMUDATA-178: ENG2_RUNNING (Functional)

### FMUDATA-179: ENG2_RUNNING_VALID (Functional)

### FMUDATA-180: FUEL_BALANCE_COMPLETE (Functional)

### FMUDATA-181: FUEL_BALANCE_VALVE_L_OPEN_CMD (Functional)

### FMUDATA-182: FUEL_BALANCE_VALVE_R_OPEN_CMD (Functional)

### FMUDATA-183: FUEL_BALANCE_VALVE_L_FULLY_OPEN (Functional)

### FMUDATA-184: FUEL_BALANCE_VALVE_L_FULLY_OPEN_VALID (Functional)

### FMUDATA-185: FUEL_BALANCE_VALVE_R_FULLY_OPEN (Functional)

### FMUDATA-186: FUEL_BALANCE_VALVE_R_FULLY_OPEN_VALID (Functional)

### FMUDATA-195: FUEL_BALANCE_VALVE_L_FULLY_CLOSED (Functional)

### FMUDATA-196: FUEL_BALANCE_VALVE_L_FULLY_CLOSED_VALID (Functional)

### FMUDATA-197: FUEL_BALANCE_VALVE_R_FULLY_CLOSED (Functional)

### FMUDATA-198: FUEL_BALANCE_VALVE_R_FULLY_CLOSED_VALID (Functional)

### FMUDATA-199: FUEL_BALANCE_VALVE_L_CLOSE_CMD (Functional)

### FMUDATA-200: FUEL_BALANCE_VALVE_R_CLOSE_CMD (Functional)

### FMUDATA-203: FUEL_IMBALANCE_DISPLAY (Functional)

### FMUDATA-204: APU_RUNNING (Functional)

### FMUDATA-205: APU_RUNNING_VALID (Functional)

### FMUDATA-210: APU_MASTER_SWITCH (Functional)

### FMUDATA-211: APU_MASTER_SWITCH_VALID (Functional)

### FMUDATA-214: APU_FIRE (Functional)

### FMUDATA-215: APU_FIRE_VALID (Functional)

### FMUDATA-218: APU_LP_VALVE_FULLY_OPEN (Functional)

### FMUDATA-219: APU_LP_VALVE_FULLY_OPEN_VALID (Functional)

### FMUDATA-222: APU_LP_VALVE_FULLY_CLOSED (Functional)

### FMUDATA-223: APU_LP_VALVE_FULLY_CLOSED_VALID (Functional)

### FMUDATA-224: APU_LP_VALVE_OPEN_CMD (Functional)

### FMUDATA-225: APU_LP_VALVE_CLOSE_CMD (Functional)

### FMUDATA-230: L_LP_MFLD_PRESSURE (Functional)

### FMUDATA-231: L_LP_MFLD_PRESSURE_VALID (Functional)

### FMUDATA-232: R_LP_MFLD_PRESSURE (Functional)

### FMUDATA-233: R_LP_MFLD_PRESSURE_VALID (Functional)

### FMUDATA-239: L_LP_MFLD_LOW_PRESSURE (Functional)

### FMUDATA-240: L_LP_MFLD_LOW_PRESSURE_RESET (Functional)

### FMUDATA-241: R_LP_MFLD_LOW_PRESSURE (Functional)

### FMUDATA-242: R_LP_MFLD_LOW_PRESSURE_RESET (Functional)

### FMUDATA-255: L_REFUEL_VALVE_FULLY_CLOSED (Functional)

### FMUDATA-256: L_REFUEL_VALVE_FULLY_CLOSED_VALID (Functional)

### FMUDATA-257: L_REFUEL_VALVE_FULLY_OPEN (Functional)

### FMUDATA-258: L_REFUEL_VALVE_FULLY_OPEN_VALID (Functional)

### FMUDATA-259: R_REFUEL_VALVE_FULLY_CLOSED (Functional)

### FMUDATA-260: R_REFUEL_VALVE_FULLY_CLOSED_VALID (Functional)

### FMUDATA-261: R_REFUEL_VALVE_FULLY_OPEN (Functional)

### FMUDATA-262: R_REFUEL_VALVE_FULLY_OPEN_VALID (Functional)

### FMUDATA-263: C_REFUEL_VALVE_FULLY_CLOSED (Functional)

### FMUDATA-264: C_REFUEL_VALVE_FULLY_CLOSED_VALID (Functional)

### FMUDATA-265: C_REFUEL_VALVE_FULLY_OPEN (Functional)

### FMUDATA-266: C_REFUEL_VALVE_FULLY_OPEN_VALID (Functional)

### FMUDATA-267: L_TK_REFUEL_SW (Functional)

### FMUDATA-268: R_TK_REFUEL_SW (Functional)

### FMUDATA-279: C_TK_REFUEL_SW (Functional)

### FMUDATA-270: TK_REFUEL_SW_VALID (Functional)

### FMUDATA-277: FUEL_XFER_MODE (Functional)

### FMUDATA-278: FUEL_XFER_MODE_VALID (Functional)

### FMUDATA-282: DEFUEL_VALVE_FULLY_OPEN (Functional)

### FMUDATA-283: DEFUEL_VALVE_FULLY_OPEN_VALID (Functional)

### FMUDATA-284: DEFUEL_VALVE_FULLY_CLOSED (Functional)

### FMUDATA-285: DEFUEL_VALVE_FULLY_CLOSED_VALID (Functional)

### FMUDATA-286: DESIRED_FUEL_LEVEL (Functional)

### FMUDATA-287: DESIRED_FUEL_LEVEL_VALID (Functional)

### FMUDATA-294: CTR_TK_HI_LEVEL (Functional)

### FMUDATA-295: CTR_TK_HI_LEVEL_VALID (Functional)

### FMUDATA-296: L_REFUEL_VALVE_CLOSE_CMD (Functional)

### FMUDATA-297: L_REFUEL_VALVE_OPEN_CMD (Functional)

### FMUDATA-298: R_REFUEL_VALVE_CLOSE_CMD (Functional)

### FMUDATA-299: R_REFUEL_VALVE_OPEN_CMD (Functional)

### FMUDATA-300: CTR_REFUEL_VALVE_CLOSE_CMD (Functional)

### FMUDATA-301: CTR_REFUEL_VALVE_OPEN_CMD (Functional)

### FMUDATA-302: FUEL_ON_BOARD (Functional)

### FMUDATA-304: FUEL_ON_BOARD_VALID (Functional)

### FMUDATA-303: AUTO_REFUEL_COMPLETE (Functional)

### FMUDATA-305: DEFUEL_VALVE_OPEN_CMD (Functional)

### FMUDATA-306: DEFUEL_VALVE_CLOSE_CMD (Functional)

### FMUDATA-348: APU_ELEC_PUMP_ENABLE (Functional)

### FMUDATA-350: ENGINE_TEMP_S2 (Functional)

### FMUDATA-351: ENGINE_TEMP_VALID_S2 (Functional)

### FMUDATA-352: OVERSPEED_FAULT (Functional)

### FMUDATA-353: AC_IN_FLIGHT (Functional)

### FMUDATA-354: AC_ON_GROUND (Functional)
