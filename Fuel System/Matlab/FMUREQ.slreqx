# FMUREQ

## #40: ISM Logic (Functional)

### FMUREQ-1776: IN_FUEL_TANK_TEMP (Functional)
FMU shall set the FUEL_TANK_TEMP_VALID to True and set FUEL_TANK_TEMP to the value of IN_FUEL_TANK_TEMP if the following evaluates to True:
(
(IN_FUEL_TANK_TEMP_ACTIVE is equal to True) AND
(
( IN_FUEL_TANK_TEMP is greater than or equal to IN_FUEL_TANK_TEMP_ICD_MIN) AND
( IN_FUEL_TANK_TEMP is less than or equal to IN_FUEL_TANK_TEMP_ICD_MAX)
)
)
Otherwise, set FUEL_TANK_TEMP_VALID to False and set FUEL_TANK_TEMP to the default value of IN_FUEL_TANK_TEMP_MIN (0 Deg C).

### FMUREQ-1782: IN_CTR_TK_FUEL_LEVEL (Functional)
FMU shall set the CTR_TK_FUEL_LEVEL_VALID to True and set CTR_TK_FUEL_LEVEL to the value of IN_CTR_TK_FUEL_LEVEL if the following evaluates to True:
(
(IN_CTR_TK_FUEL_LEVEL_ACTIVE is equal to True) AND
(
( IN_CTR_TK_FUEL_LEVEL is greater than or equal to IN_CTR_TK_FUEL_LEVEL_ICD_MIN) OR
( IN_CTR_TK_FUEL_LEVEL is less than or equal to IN_CTR_TK_FUEL_LEVEL_ICD_MAX)
)
)
Otherwise, set the CTR_TK_FUEL_LEVEL_VALID to False and set CTR_TK_FUEL_LEVEL to IN_FUEL_LEVEL_ICD_MIN.

### FMUREQ-1784: IN_RECORDED_SPEED (Functional)
FMU shall set the RECORDED_SPEED_VALID to True and set RECORDED_SPEED to the value of IN_RECORDED_SPEED if the following evaluates to True:
(
(IN_RECORDED_SPEED_ACTIVE is equal to True) AND
(
(IN_RECORDED_SPEED is greater than or equal to IN_RECORDED_SPEED_ICD_MIN) OR
(IN_RECORDED_SPEED is less than or equal to IN_RECORDED_SPEED_ICD_MAX)
)
)
Otherwise, set RECORDED_SPEED_VALID to False and set RECORDED_SPEED to IN_RECORDED_SPEED_ICD_MIN.

### FMUREQ-1790: IN_GROUND_SPEED (Functional)
FMU shall set the GROUND_SPEED_VALID to True and set GROUND_SPEED to the value of IN_GROUND_SPEED if the following evaluates to True:
(
(IN_GROUND_SPEED_ACTIVE is equal to True) AND
(
(IN_GROUND_SPEED is greater than or equal to IN_GROUND_SPEED_ICD_MIN) AND
(IN_GROUND_SPEED is less than or equal to IN_GROUND_SPEED_ICD_MAX)
)
)
Otherwise, set GROUND_SPEED_VALID to False and set GROUND_SPEED to the default value of IN_GROUND_SPEED_ICD_MIN (0 mph).

### FMUREQ-1791: IN_BRAKE_SENSOR_STATUS (Functional)
FMU shall set BRAKE_SENSOR_STATUS_VALID to True and set BRAKE_SENSOR_STATUS to the value of IN_BRAKE_SENSOR_STATUS if the following evaluates to True:
(
(IN_BRAKE_SENSOR_STATUS_ACTIVE is equal to True)
)
Otherwise, set BRAKE_SENSOR_STATUS_VALID to False and set BRAKE_SENSOR_STATUS to BRAKES_NOT_APPLIED.

### FMUREQ-1794: IN_ON_GROUND (Functional)
FMU shall set ON_GROUND_VALID to True and set ON_GROUND to the value of IN_ON_GROUND if the following evaluates to True:
(
(IN_ON_GROUND_ACTIVE is equal to True)
)
Otherwise, set ON_GROUND_VALID to False and set ON_GROUND to False.

### #10: IN_ENGINE_TEMP_Sx (Container)

#### FMUREQ-1793: IN_ENGINE_TEMP_S2 (Functional)
FMU shall set the ENGINE_TEMP_VALID_S2 to True and set ENGINE_TEMP_S2 to the value of IN_ENGINE_TEMP_S2 if the following evaluates to True:
(
(IN_ENGINE_TEMP_ACTIVE_S2 is equal to True) AND
(
(IN_ENGINE_TEMP_S2 is greater than or equal to IN_ENGINE_TEMP_ICD_MIN) AND
(IN_ENGINE_TEMP_S2 is less than or equal to IN_ENGINE_TEMP_ICD_MAX)
)
)
Otherwise, set ENGINE_TEMP_VALID_S2 to False and set ENGINE_TEMP_S2 to the default value of IN_ENGINE_TEMP_MIN (0 Deg C).

#### FMUREQ-1792: IN_ENGINE_TEMP_S1 (Functional)
FMU shall set the ENGINE_TEMP_VALID_S1 to True and set ENGINE_TEMP_S1 to the value of IN_ENGINE_TEMP_S1 if the following evaluates to True:
(
(IN_ENGINE_TEMP_ACTIVE_S1 is equal to True) AND
(
(IN_ENGINE_TEMP_S1 is greater than or equal to IN_ENGINE_TEMP_ICD_MIN) AND
(IN_ENGINE_TEMP_S1 is less than or equal to IN_ENGINE_TEMP_ICD_MAX)
)
)
Otherwise, set ENGINE_TEMP_VALID_S1 to False and set ENGINE_TEMP_S1 to the default value of IN_ENGINE_TEMP_MIN (0 Deg C).

### #12: IN_PBIT_STATUS (Container)

#### FMUREQ-1780: IN_PBIT_STATUS (Functional)
FMU shall set the PBIT_STATUS_VALID to True and set PBIT_STATUS to the value of IN_PBIT_STATUS if the following evaluates to True:
(
(IN_PBIT_STATUS_ACTIVE is equal to True)
)

#### FMUREQ-1781: IN_PBIT_STATUS (Functional)
FMU shall set the PBIT_STATUS_VALID to False and set PBIT_STATUS to False if the following evaluates to True:
(
(IN_PBIT_STATUS_ACTIVE is equal to False)
)

### FMUREQ-1798: IN_FAULT_IGNORE (Functional)
FMU shall set FAULT_IGNORE_VALID to True and set FAULT_IGNORE to the value of IN_FAULT_IGNORE if the following logic evaluates to True:
(
(IN_FAULT_IGNORE_ACTIVE is equal to True)
)
Otherwise, set FAULT_IGNORE_VALID to False and set FAULT_IGNORE to False.

### FMUREQ-1806: IN_FLIGHT_PHASE (Functional)
FMU software shall set FLIGHT_PHASE_VALID to True and set FLIGHT_PHASE to the value of IN_FLIGHT_PHASE if the following logic evaluates to True:
(
(IN_FLIGHT_PHASE_ACTIVE is equal to True) AND
(
(IN_FLIGHT_PHASE is greater than or equal to IN_FLIGHT_PHASE_ICD_MIN) AND
(IN_FLIGHT_PHASE is less than or equal to IN_FLIGHT_PHASE_ICD_MAX)
)
)
Otherwise, set FLIGHT_PHASE_VALID to False and maintain the previous value of FLIGHT_PHASE.
Note: Flight phase key
1. Pre-flight
2. Taxi
3. Takeoff
4. Climb
5. Cruise
6. Descent
7. Landing
8. Post-flight

### FMUREQ-1809: IN_CTR_TK_MAN_SWITCH (Functional)
FMU Software shall set CTR_TK_MAN_SWITCH_VALID to True and set CTR_TK_MAN_SWITCH to the value of IN_CTR_TK_MAN_SWITCH if the following logic evaluates to True:
(
(IN_CTR_TK_MAN_SWITCH_ACTIVE is equal to True)
)
Otherwise, set CTR_TK_MAN_SWITCH_VALID to False and maintain the previous value of CTR_TK_MAN_SWITCH.

### #17: IN_CTR_TK_PUMP_x_SWITCH (Container)

#### FMUREQ-1810: IN_CTR_TK_PUMP_1_SWITCH (Functional)
FMU Software shall set CTR_TK_PUMP_1_SWITCH_VALID to True and set CTR_TK_PUMP_1_SWITCH to the value of IN_CTR_TK_PUMP_1_SWITCH if the following logic evaluates to True:
(
(IN_CTR_TK_PUMP_1_SWITCH_ACTIVE is equal to True)
)
Otherwise, set CTR_TK_PUMP_1_SWITCH_VALID to False and maintain the previous value of CTR_TK_PUMP_1_SWITCH.

#### FMUREQ-1811: IN_CTR_TK_PUMP_2_SWITCH (Functional)
FMU Software shall set CTR_TK_PUMP_2_SWITCH_VALID to True and set CTR_TK_PUMP_2_SWITCH to the value of IN_CTR_TK_PUMP_2_SWITCH if the following logic evaluates to True:
(
(IN_CTR_TK_PUMP_2_SWITCH_ACTIVE is equal to True)
)
Otherwise, set CTR_TK_PUMP_2_SWITCH_VALID to False and maintain the previous value of CTR_TK_PUMP_2_SWITCH.

### FMUREQ-1814: IN_CTR_TK_LOW_LEVEL (Functional)
FMU Software shall set CTR_TK_LOW_LEVEL_VALID to True and set CTR_TK_LOW_LEVEL to the value of IN_CTR_TK_LOW_LEVEL if the following logic evaluates to True:
(
(IN_CTR_TK_LOW_LEVEL_ACTIVE is equal to True)
)
Otherwise, set CTR_TK_LOW_LEVEL_VALID to False and maintain the previous value of CTR_TK_LOW_LEVEL.

### #21: IN_x_TK_LOW_LEVEL (Container)

#### FMUREQ-1815: IN_L_TK_LOW_LEVEL (Functional)
FMU Software shall set L_TK_LOW_LEVEL_VALID to True and set L_TK_LOW_LEVEL to the value of IN_L_TK_LOW_LEVEL if the following logic evaluates to True:
(
(IN_L_TK_LOW_LEVEL_ACTIVE is equal to True)
)
Otherwise, set L_TK_LOW_LEVEL_VALID to False and maintain the previous value of L_TK_LOW_LEVEL.

#### FMUREQ-1816: IN_R_TK_LOW_LEVEL (Functional)
FMU Software shall set R_TK_LOW_LEVEL_VALID to True and set R_TK_LOW_LEVEL to the value of IN_R_TK_LOW_LEVEL if the following logic evaluates to True:
(
(IN_R_TK_LOW_LEVEL_ACTIVE is equal to True)
)
Otherwise, set R_TK_LOW_LEVEL_VALID to False and maintain the previous value of R_TK_LOW_LEVEL.

### #24: IN_x_TK_HI_LEVEL (Container)

#### FMUREQ-1817: IN_L_TK_HI_LEVEL (Functional)
FMU Software shall set L_TK_HI_LEVEL_VALID to True and set L_TK_HI_LEVEL to the value of IN_L_TK_HI_LEVEL if the following logic evaluates to True:
(
(IN_L_TK_HI_LEVEL_ACTIVE is equal to True)
)
Otherwise, set L_TK_HI_LEVEL_VALID to False and maintain the previous value of L_TK_HI_LEVEL.

#### FMUREQ-1818: IN_R_TK_HI_LEVEL (Functional)
FMU Software shall set R_TK_HI_LEVEL_VALID to True and set R_TK_HI_LEVEL to the value of IN_R_TK_HI_LEVEL if the following logic evaluates to True:
(
(IN_R_TK_HI_LEVEL_ACTIVE is equal to True)
)
Otherwise, set R_TK_HI_LEVEL_VALID to False and maintain the previous value of R_TK_HI_LEVEL.

#### FMUREQ-1876: IN_CTR_TK_HI_LEVEL (Functional)
FMU Software shall set CTR_TK_HI_LEVEL_VALID to True and set CTR_TK_HI_LEVEL to the value of IN_CTR_TK_HI_LEVEL if the following logic evaluates to True:
(
(IN_CTR_TK_HI_LEVEL_ACTIVE is equal to True)
)
Otherwise, set CTR_TK_HI_LEVEL_VALID to False and maintain the previous value of CTR_TK_HI_LEVEL.

### #28: IN_x_TK_PUMP_y_SWITCH (Container)

#### FMUREQ-1819: IN_L_TK_PUMP_1_SWITCH (Functional)
FMU Software shall set L_TK_PUMP_1_SWITCH_VALID to True and set L_TK_PUMP_1_SWITCH to the value of IN_L_TK_PUMP_1_SWITCH if the following logic evaluates to True:
(
(IN_L_TK_PUMP_1_SWITCH_ACTIVE is equal to True)
)
Otherwise, set L_TK_PUMP_1_SWITCH_VALID to False and maintain the previous value of L_TK_PUMP_1_SWITCH.

#### FMUREQ-1820: IN_L_TK_PUMP_2_SWITCH (Functional)
FMU Software shall set L_TK_PUMP_2_SWITCH_VALID to True and set L_TK_PUMP_2_SWITCH to the value of IN_L_TK_PUMP_2_SWITCH if the following logic evaluates to True:
(
(IN_L_TK_PUMP_2_SWITCH_ACTIVE is equal to True)
)
Otherwise, set L_TK_PUMP_2_SWITCH_VALID to False and maintain the previous value of L_TK_PUMP_2_SWITCH.

#### FMUREQ-1821: IN_R_TK_PUMP_1_SWITCH (Functional)
FMU Software shall set R_TK_PUMP_1_SWITCH_VALID to True and set R_TK_PUMP_1_SWITCH to the value of IN_R_TK_PUMP_1_SWITCH if the following logic evaluates to True:
(
(IN_R_TK_PUMP_1_SWITCH_ACTIVE is equal to True)
)
Otherwise, set R_TK_PUMP_1_SWITCH_VALID to False and maintain the previous value of R_TK_PUMP_1_SWITCH.

#### FMUREQ-1822: IN_R_TK_PUMP_2_SWITCH (Functional)
FMU Software shall set R_TK_PUMP_2_SWITCH_VALID to True and set R_TK_PUMP_2_SWITCH to the value of IN_R_TK_PUMP_2_SWITCH if the following logic evaluates to True:
(
(IN_R_TK_PUMP_2_SWITCH_ACTIVE is equal to True)
)
Otherwise, set R_TK_PUMP_2_SWITCH_VALID to False and maintain the previous value of R_TK_PUMP_2_SWITCH.

### FMUREQ-1827: IN_XFEED_VALVE_SWITCH (Functional)
FMU Software shall set XFEED_VALVE_SWITCH_VALID to True and set XFEED_VALVE_SWITCH to the value of IN_XFEED_VALVE_SWITCH if the following logic evaluates to True:
(
(IN_XFEED_VALVE_SWITCH_ACTIVE is equal to True)
)
Otherwise, set XFEED_VALVE_SWITCH_VALID to True and maintain the previous value of XFEED_VALVE_SWITCH.

### FMUREQ-1830: IN_XFEED_VALVE_FULLY_CLOSED (Functional)
FMU Software shall set XFEED_VALVE_FULLY_CLOSED_VALID to True and set XFEED_VALVE_FULLY_CLOSED to the value of IN_XFEED_VALVE_FULLY_CLOSED if the following logic evaluates to True:
(
(IN_XFEED_VALVE_FULLY_CLOSED_ACTIVE is equal to True)
)
Otherwise, set XFEED_VALVE_FULLY_CLOSED_VALID to True and maintain the previous value of XFEED_VALVE_FULLY_CLOSED.

### FMUREQ-1831: IN_XFEED_VALVE_FULLY_OPEN (Functional)
FMU Software shall set XFEED_VALVE_FULLY_OPEN_VALID to True and set XFEED_VALVE_FULLY_OPEN to the value of IN_XFEED_VALVE_FULLY_OPEN if the following logic evaluates to True:
(
(IN_XFEED_VALVE_FULLY_OPEN_ACTIVE is equal to True)
)
Otherwise, set XFEED_VALVE_FULLY_OPEN_VALID to True and maintain the previous value of XFEED_VALVE_FULLY_OPEN.

### FMUREQ-1832: IN_FUEL_BALANCE_PB (Functional)
FMU Software shall set FUEL_BALANCE_PB_VALID to True and set FUEL_BALANCE_PB to the value of IN_FUEL_BALANCE_PB if the following logic evaluates to True:
(
(IN_FUEL_BALANCE_PB_ACTIVE is equal to True)
)
Otherwise, set FUEL_BALANCE_PB_VALID to False and maintain the previous value of FUEL_BALANCE_PB.

### #37: IN_x_TK_FUEL_LEVEL (Container)

#### FMUREQ-1836: IN_L_TK_FUEL_LEVEL (Functional)
FMU Software shall set L_TK_FUEL_LEVEL_VALID to True and set L_TK_FUEL_LEVEL to the value of IN_L_TK_FUEL_LEVEL if the following logic evaluates to True:
(
(IN_L_TK_FUEL_LEVEL_ACTIVE is equal to True) AND
(
(IN_L_TK_FUEL_LEVEL is greater than or equal to WING_TK_FUEL_LEVEL_ICD_MIN) AND
(IN_L_TK_FUEL_LEVEL is less than or equal to WING_TK_FUEL_LEVEL_ICD_MAX)
)
)
Otherwise, set L_TK_FUEL_LEVEL_VALID to False and maintain the previous value of L_TK_FUEL_LEVEL.

#### FMUREQ-1837: IN_R_TK_FUEL_LEVEL (Functional)
FMU Software shall set R_TK_FUEL_LEVEL_VALID to True and set R_TK_FUEL_LEVEL to the value of IN_R_TK_FUEL_LEVEL if the following logic evaluates to True:
(
(IN_R_TK_FUEL_LEVEL_ACTIVE is equal to True) AND
(
(IN_R_TK_FUEL_LEVEL is greater than or equal to WING_TK_FUEL_LEVEL_ICD_MIN) AND
(IN_R_TK_FUEL_LEVEL is less than or equal to WING_TK_FUEL_LEVEL_ICD_MAX)
)
)
Otherwise, set R_TK_FUEL_LEVEL_VALID to False and maintain the previous value of R_TK_FUEL_LEVEL.

### #41: IN_ENG_x_RUNNING (Container)

#### FMUREQ-1842: IN_ENG1_RUNNING (Functional)
FMU Software shall set ENG1_RUNNING_VALID to True and set ENG1_RUNNING to the value of IN_ENG1_RUNNING if the following logic evaluates to True:
(
(IN_ENG1_RUNNING_ACTIVE is equal to True)
)
Otherwise, set ENG1_RUNNING_VALID to False and maintain the previous value of ENG1_RUNNING.

#### FMUREQ-1843: IN_ENG2_RUNNING (Functional)
FMU Software shall set ENG2_RUNNING_VALID to True and set ENG2_RUNNING to the value of IN_ENG2_RUNNING if the following logic evaluates to True:
(
(IN_ENG2_RUNNING_ACTIVE is equal to True)
)
Otherwise, set ENG2_RUNNING_VALID to False and maintain the previous value of ENG2_RUNNING.

### FMUREQ-1851: IN_APU_RUNNING (Functional)
FMU Software shall set APU_RUNNING_VALID to True and set APU_RUNNING to the value of IN_APU_RUNNING if the following logic evaluates to True:
(
(IN_APU_RUNNING_ACTIVE is equal to True)
)
Otherwise, set APU_RUNNING_VALID to False and maintain the previous value of APU_RUNNING.

### #45: IN_FUEL_BALANCE_VALVE_x_FULLY_OPEN (Container)

#### FMUREQ-1844: IN_FUEL_BALANCE_VALVE_L_FULLY_OPEN (Functional)
FMU Software shall set FUEL_BALANCE_VALVE_L_FULLY_OPEN_VALID to True and set FUEL_BALANCE_VALVE_L_FULLY_OPEN to the value of IN_FUEL_BALANCE_VALVE_L_FULLY_OPEN if the following logic evaluates to True:
(
(IN_FUEL_BALANCE_VALVE_L_FULLY_OPEN_ACTIVE is equal to True)
)
Otherwise, set FUEL_BALANCE_VALVE_L_FULLY_OPEN_VALID to True and maintain the previous value of FUEL_BALANCE_VALVE_L_FULLY_OPEN.

#### FMUREQ-1845: IN_FUEL_BALANCE_VALVE_R_FULLY_OPEN (Functional)
FMU Software shall set FUEL_BALANCE_VALVE_R_FULLY_OPEN_VALID to True and set FUEL_BALANCE_VALVE_R_FULLY_OPEN to the value of IN_FUEL_BALANCE_VALVE_R_FULLY_OPEN if the following logic evaluates to True:
(
(IN_FUEL_BALANCE_VALVE_R_FULLY_OPEN_ACTIVE is equal to True)
)
Otherwise, set FUEL_BALANCE_VALVE_R_FULLY_OPEN_VALID to True and maintain the previous value of FUEL_BALANCE_VALVE_R_FULLY_OPEN.

### #48: IN_FUEL_BALANCE_VALVE_x_FULLY_CLOSED (Container)

#### FMUREQ-1846: IN_FUEL_BALANCE_VALVE_L_FULLY_CLOSED (Functional)
FMU Software shall set FUEL_BALANCE_VALVE_L_FULLY_CLOSED_VALID to True and set FUEL_BALANCE_VALVE_L_FULLY_CLOSED to the value of IN_FUEL_BALANCE_VALVE_L_FULLY_CLOSED if the following logic evaluates to True:
(
(IN_FUEL_BALANCE_VALVE_L_FULLY_CLOSED_ACTIVE is equal to True)
)
Otherwise, set FUEL_BALANCE_VALVE_L_FULLY_CLOSED_VALID to True and maintain the previous value of FUEL_BALANCE_VALVE_L_FULLY_CLOSED.

#### FMUREQ-1847: IN_FUEL_BALANCE_VALVE_R_FULLY_CLOSED (Functional)
FMU Software shall set FUEL_BALANCE_VALVE_R_FULLY_CLOSED_VALID to True and set FUEL_BALANCE_VALVE_R_FULLY_CLOSED to the value of IN_FUEL_BALANCE_VALVE_R_FULLY_CLOSED if the following logic evaluates to True:
(
(IN_FUEL_BALANCE_VALVE_R_FULLY_CLOSED_ACTIVE is equal to True)
)
Otherwise, set FUEL_BALANCE_VALVE_R_FULLY_CLOSED_VALID to True and maintain the previous value of FUEL_BALANCE_VALVE_R_FULLY_CLOSED.

### FMUREQ-1852: IN_APU_MASTER_SWITCH (Functional)
FMU software shall set APU_MASTER_SWITCH_VALID to True and set APU_MASTER_SWITCH to the value of IN_APU_MASTER_SWITCH if the following logic evaluates to True:
(
(IN_APU_MASTER_SWITCH_ACTIVE is equal to True)
)
Otherwise, set APU_MASTER_SWITCH_VALID to False and maintain the previous value of APU_MASTER_SWITCH.

### FMUREQ-1853: IN_APU_FIRE (Functional)
FMU software shall set APU_FIRE_VALID to True and set APU_FIRE to the value of IN_APU_FIRE if the following logic evaluates to True:
(
(IN_APU_FIRE_ACTIVE is equal to True)
)
Otherwise, set APU_FIRE_VALID to False and maintain the previous value of APU_FIRE.

### FMUREQ-1854: IN_APU_LP_VALVE_FULLY_OPEN (Functional)
FMU software shall set APU_LP_VALVE_FULLY_OPEN_VALID to True and set APU_LP_VALVE_FULLY_OPEN to the value of IN_APU_LP_VALVE_FULLY_OPEN if the following logic evaluates to True:
(
(IN_APU_LP_VALVE_FULLY_OPEN_ACTIVE is equal to True)
)
Otherwise, set APU_LP_VALVE_FULLY_OPEN_VALID to False and maintain the previous value of APU_LP_VALVE_FULLY_OPEN.

### FMUREQ-1855: IN_APU_LP_VALVE_FULLY_CLOSED (Functional)
FMU software shall set APU_LP_VALVE_FULLY_CLOSED_VALID to True and set APU_LP_VALVE_FULLY_CLOSED to the value of IN_APU_LP_VALVE_FULLY_CLOSED if the following logic evaluates to True:
(
(IN_APU_LP_VALVE_FULLY_CLOSED_ACTIVE is equal to True)
)
Otherwise, set APU_LP_VALVE_FULLY_CLOSED_VALID to False and maintain the previous value of APU_LP_VALVE_FULLY_CLOSED.

### #55: IN_x_LP_MFLD_PRESSURE (Container)

#### FMUREQ-1859: IN_L_LP_MFLD_PRESSURE (Functional)
FMU shall set L_LP_MFLD_PRESSURE_VALID to True and set L_LP_MFLD_PRESSURE to the value of IN_L_LP_MFLD_PRESSURE if the following logic evaluates to True:
(
(IN_L_LP_MFLD_PRESSURE_ACTIVE is equal to True) AND
(IN_L_LP_MFLD_PRESSURE is greater than or equal to LP_MFLD_PRESSURE_ICD_MIN) AND
(IN_L_LP_MFLD_PRESSURE is less than or equal to LP_MFLD_PRESSURE_ICD_MAX)
)
Otherwise, set L_LP_MFLD_PRESSURE_VALID to False and maintain the previous value of L_LP_MFLD_PRESSURE.

#### FMUREQ-1860: IN_R_LP_MFLD_PRESSURE (Functional)
FMU shall set R_LP_MFLD_PRESSURE_VALID to True and set R_LP_MFLD_PRESSURE to the value of IN_R_LP_MFLD_PRESSURE if the following logic evaluates to True:
(
(IN_R_LP_MFLD_PRESSURE_ACTIVE is equal to True) AND
(IN_R_LP_MFLD_PRESSURE is greater than or equal to LP_MFLD_PRESSURE_ICD_MIN) AND
(IN_R_LP_MFLD_PRESSURE is less than or equal to LP_MFLD_PRESSURE_ICD_MAX)
)
Otherwise, set R_LP_MFLD_PRESSURE_VALID to False and maintain the previous value of R_LP_MFLD_PRESSURE.

### #58: IN_x_REFUEL_VALVE_FULLY_OPEN (Container)

#### FMUREQ-1865: IN_L_REFUEL_VALVE_FULLY_OPEN (Functional)
FMU software shall set L_REFUEL_VALVE_FULLY_OPEN_VALID to True and set L_REFUEL_VALVE_FULLY_OPEN to the value of IN_L_REFUEL_VALVE_FULLY_OPEN if the following logic evaluates to True:
(
(IN_L_REFUEL_VALVE_FULLY_OPEN_ACTIVE is equal to True)
)
Otherwise, set L_REFUEL_VALVE_FULLY_OPEN_VALID to False and maintain the previous value of L_REFUEL_VALVE_FULLY_OPEN.

#### FMUREQ-1866: IN_R_REFUEL_VALVE_FULLY_OPEN (Functional)
FMU software shall set R_REFUEL_VALVE_FULLY_OPEN_VALID to True and set R_REFUEL_VALVE_FULLY_OPEN to the value of IN_R_REFUEL_VALVE_FULLY_OPEN if the following logic evaluates to True:
(
(IN_R_REFUEL_VALVE_FULLY_OPEN_ACTIVE is equal to True)
)
Otherwise, set R_REFUEL_VALVE_FULLY_OPEN_VALID to False and maintain the previous value of R_REFUEL_VALVE_FULLY_OPEN.

#### FMUREQ-1867: IN_C_REFUEL_VALVE_FULLY_OPEN (Functional)
FMU software shall set C_REFUEL_VALVE_FULLY_OPEN_VALID to True and set C_REFUEL_VALVE_FULLY_OPEN to the value of IN_C_REFUEL_VALVE_FULLY_OPEN if the following logic evaluates to True:
(
(IN_C_REFUEL_VALVE_FULLY_OPEN_ACTIVE is equal to True)
)
Otherwise, set C_REFUEL_VALVE_FULLY_OPEN_VALID to False and maintain the previous value of C_REFUEL_VALVE_FULLY_OPEN.

### #62: IN_x_REFUEL_VALVE_FULLY_CLOSED (Container)

#### FMUREQ-1868: IN_L_REFUEL_VALVE_FULLY_CLOSED (Functional)
FMU software shall set L_REFUEL_VALVE_FULLY_CLOSED_VALID to True and set L_REFUEL_VALVE_FULLY_CLOSED to the value of IN_L_REFUEL_VALVE_FULLY_CLOSED if the following logic evaluates to True:
(
(IN_L_REFUEL_VALVE_FULLY_CLOSED_ACTIVE is equal to True)
)
Otherwise, set L_REFUEL_VALVE_FULLY_CLOSED_VALID to False and maintain the previous value of L_REFUEL_VALVE_FULLY_CLOSED.

#### FMUREQ-1869: IN_R_REFUEL_VALVE_FULLY_CLOSED (Functional)
FMU software shall set R_REFUEL_VALVE_FULLY_CLOSED_VALID to True and set R_REFUEL_VALVE_FULLY_CLOSED to the value of IN_R_REFUEL_VALVE_FULLY_CLOSED if the following logic evaluates to True:
(
(IN_R_REFUEL_VALVE_FULLY_CLOSED_ACTIVE is equal to True)
)
Otherwise, set R_REFUEL_VALVE_FULLY_CLOSED_VALID to False and maintain the previous value of R_REFUEL_VALVE_FULLY_CLOSED.

#### FMUREQ-1870: IN_C_REFUEL_VALVE_FULLY_CLOSED (Functional)
FMU software shall set C_REFUEL_VALVE_FULLY_CLOSED_VALID to True and set C_REFUEL_VALVE_FULLY_CLOSED to the value of IN_C_REFUEL_VALVE_FULLY_CLOSED if the following logic evaluates to True:
(
(IN_C_REFUEL_VALVE_FULLY_CLOSED_ACTIVE is equal to True)
)
Otherwise, set C_REFUEL_VALVE_FULLY_CLOSED_VALID to False and maintain the previous value of C_REFUEL_VALVE_FULLY_CLOSED.

### FMUREQ-1871: IN_x_TK_REFUEL_SWITCH (Functional)
FMU software shall set TK_REFUEL_SW_VALID to True and set the following signals:
L_TK_REFUEL_SW to IN_L_TK_REFUEL_SW
R_TK_REFUEL_SW to IN_R_TK_REFUEL_SW
C_TK_REFUEL_SW to IN_C_TK_REFUEL_SW
if the following logic evaluates to True:
(
(IN_TK_REFUEL_SW_ACTIVE is equal to True)
)
Otherwise, set L_TK_REFUEL_SW_VALID to False and maintain the previous value of L_TK_REFUEL_SW.

### FMUREQ-1872: IN_FUEL_XFER_MODE (Functional)
FMU software shall set FUEL_XFER_MODE_VALID to True and set FUEL_XFER_MODE to the value of IN_FUEL_XFER_MODE if the following logic evaluates to True:
(
(IN_FUEL_XFER_MODE_ACTIVE is equal to True) AND
(
(IN_FUEL_XFER_MODE is equal to XM_OFF) OR
(IN_FUEL_XFER_MODE is equal to XM_MAN) OR
(IN_FUEL_XFER_MODE is equal to XM_AUTO) OR
(IN_FUEL_XFER_MODE is equal to XM_DEFUEL)
)
)
Otherwise, set FUEL_XFER_MODE_VALID to False and set FUEL_XFER_MODE to XM_OFF.

### FMUREQ-1873: IN_DEFUEL_VALVE_FULLY_OPEN (Functional)
FMU software shall set DEFUEL_VALVE_FULLY_OPEN_VALID to True and set DEFUEL_VALVE_FULLY_OPEN to the value of IN_DEFUEL_VALVE_FULLY_OPEN if the following logic evaluates to True:
(
(IN_DEFUEL_VALVE_ACTIVE is equal to True)
)
Otherwise, set DEFUEL_VALVE_FULLY_OPEN_VALID to False and maintain the previous value of DEFUEL_VALVE_FULLY_OPEN.

### FMUREQ-1874: IN_DEFUEL_VALVE_FULLY_CLOSED (Functional)
FMU software shall set DEFUEL_VALVE_FULLY_CLOSED_VALID to True and set DEFUEL_VALVE_FULLY_CLOSED to the value of IN_DEFUEL_VALVE_FULLY_CLOSED if the following logic evaluates to True:
(
(IN_DEFUEL_VALVE_ACTIVE is equal to True)
)
Otherwise, set DEFUEL_VALVE_FULLY_CLOSED_VALID to False and maintain the previous value of DEFUEL_VALVE_FULLY_CLOSED.

### FMUREQ-1875: IN_DESIRED_FUEL_LEVEL (Functional)
FMU software shall set DESIRED_FUEL_LEVEL_VALID to True and set DESIRED_FUEL_LEVEL to the value of IN_DESIRED_FUEL_LEVEL if the following logic evaluates to True:
(
(IN_DESIRED_FUEL_LEVEL_ACTIVE is equal to True) AND
(IN_DESIRED_FUEL_LEVEL is greater than or equal to IN_FUEL_LEVEL_ICD_MIN) AND
(IN_DESIRED_FUEL_LEVEL is less than or equal to IN_FUEL_LEVEL_ICD_MAX)
)
Otherwise, set DESIRED_FUEL_LEVEL_VALID to False and maintain the previous value of DESIRED_FUEL_LEVEL.

## #71: Monitoring Logic (Container)

### #72: FUEL_TANK_OVHT_LATCHED (Container)

#### FMUREQ-1777: FUEL_TANK_OVHT_LATCHED True (Functional)
FMU shall set the FUEL_TANK_OVHT_LATCHED to True if the following logic evaluates to True:
(
(FUEL_TANK_OVHT_RESET is equal to False) AND
(
(FUEL_TANK_TEMP is greater than FUEL_TANK_TEMP_OVHT_TH_SET ) AND
(FUEL_TANK_TEMP_VALID is equal to True)
) is equal to True unchanged for greater than FUEL_TANK_TEMP_OVHT_SET_DELAY
)
otherwise, maintain the previous value of FUEL_TANK_OVHT_LATCHED if the following logic evaluates to True:
(
(FUEL_TANK_OVHT_RESET is equal to False)
)

#### FMUREQ-1778: FUEL_TANK_OVHT_LATCHED False (Functional)
FMU shall set the FUEL_TANK_OVHT_LATCHED to False if the following logic evaluates to True:
(
(FUEL_TANK_OVHT_RESET is equal to True)
)

#### FMUREQ-1779: FUEL_TANK_OVHT_RESET (Functional)
FMU shall set the FUEL_TANK_OVHT_RESET to True if the following logic evaluates to True:
(
(
(FUEL_TANK_TEMP is less than FUEL_TANK_TEMP_OVHT_TH_RESET ) AND
(FUEL_TANK_TEMP_VALID is equal to True)
) is equal to True unchanged for greater than FUEL_TANK_TEMP_OVHT_RESET_DELAY
)
otherwise, set FUEL_TANK_OVHT_RESET to False.

### FMUREQ-1783: FUEL_LEVEL_XDCR_FAULT (Functional)
FMU shall set the FUEL_LEVEL_XCDR_FAULT to True if the following evaluates to True:
(
(CTR_TK_FUEL_LEVEL_VALID is equal to False)
)
Otherwise, set the FUEL_LEVEL_XCDR_FAULT to False.

### FMUREQ-1799: AUTO_FAULT_DETECT_ENABLED (Functional)
FMU shall set AUTO_FAULT_DETECT_ENABLED to True if the following evaluates to True:
(
(
(PBIT_STATUS is equal to True) AND
(PBIT_STATUS_VALID is equal to True)
) AND
(
(RECORDED_SPEED is greater than IN_FLIGHT_TH) AND
(RECORDED_SPEED_VALID is equal to True)
) is True for greater than STABLE_FLIGHT_DELAY AND
(
(ON_GROUND is equal to False) AND
(ON_GROUND_VALID is equal to True)
)
)
Otherwise, set AUTO_FAULT_DETECT_ENABLED to False.

### FMUREQ-1786: FUEL_LEVEL_DETECT_VALUE_1 (Functional)
FMU shall set the FUEL_LEVEL_LEAK_DETECT_VALUE_1 to CTR_TK_FUEL_LEVEL and set FUEL_LEVEL_LEAK_DETECT_VALUE_1_VALID to True if the following evaluates to True:
(
(
(CTR_TK_FUEL_LEVEL_VALID is equal to True)AND
(FUEL_LEVEL_LEAK_DETECT_VALUE_2_VALID is equal to False)
) is equal to True for greater than LEAK_DETECTION_DELAY AND
(FAULT_DETECT_ENABLED is equal to True)
)
Otherwise, maintain the previous value FUEL_LEVEL_LEAK_DETECT_VALUE_1 and FUEL_LEVEL_LEAK_DETECT_VALUE_1_VALID to False.
Note: FUEL_LEVEL_LEAK_DETECT_VALUE_1 default value FUEL_LEVEL_MIN = 0

### FMUREQ-1787: FUEL_LEVEL_DETECT_VALUE_2 (Functional)
FMU shall set the FUEL_LEVEL_LEAK_DETECT_VALUE_2 to CTR_TK_FUEL_LEVEL and set FUEL_LEVEL_LEAK_DETECT_VALUE_2_VALID to True if the following evaluates to True:
(
(
(CTR_TK_FUEL_LEVEL_VALID is equal to True) AND
(FUEL_LEVEL_LEAK_DETECT_VALUE_1_VALID is equal to True)
) equal to True for greater than LEAK_DETECTION_DELAY AND
(FAULT_DETECT_ENABLED is equal to True)
)
Otherwise, maintain the previous value of FUEL_LEVEL_LEAK_DETECT_VALUE_2 and FUEL_LEVEL_LEAK_DETECT_VALUE_2_VALID to False.
Note: FUEL_LEVEL_LEAK_DETECT_VALUE_2 default value FUEL_LEVEL_MAX = 1000

### FMUREQ-1788: FUEL_LEVEL_LEAK (Functional)
FMU shall set the FUEL_LEVEL_LEAK to True if the following evaluates to True:
(
((FUEL_LEVEL_LEAK_DETECT_VALUE_2 - FUEL_LEVEL_LEAK_DETECT_VALUE_1) is greater than LEAK_DETECT_THRESHOLD) AND
(FAULT_DETECT_ENABLED is equal to True for greater than LEAK_DETECTION_DELAY2)
)
Otherwise, set FUEL_LEVEL_LEAK to False.

### FMUREQ-1789: AC_NO_GO (Functional)
FMU shall set the AC_NO_GO to True if the following evaluates to True:
(
(FUEL_TANK_OVHT_LATCHED is equal to True) OR
(FUEL_LEVEL_LEAK is equal to True) OR
(FUEL_LEVEL_XDCR_FAULT is equal to True) OR
(OVERSPEED_FAULT is equal to True)
)
Otherwise, set AC_NO_GO to False

### FMUREQ-1795: OVERSPEED_FAULT (Functional)
FMU shall set OVERSPEED_FAULT to True if the following evaluates to True:
(
(BRAKE_SENSOR_STATUS is equal to BRAKES_APPLIED) AND
(BRAKE_SENSOR_STATUS_VALID is equal to True) AND
(
(RECORDED_SPEED is greater than IN_FLIGHT_TH) AND
(RECORDED_SPEED_VALID is True)
) is equal to True unchanged for greater than OVERSPEED_FAULT_DELAY AND
(FAULT_DETECT_ENABLED is equal to True) AND
(ON_GROUND is equal to True) AND
(ON_GROUND_VALID is equal to True)
)
Otherwise, set OVERSPEED_FAULT to False.

### FMUREQ-1796: AC_IN_FLIGHT (Functional)
FMU software shall set AC_IN_FLIGHT to True if the following evaluates to True:
(
(ON_GROUND is equal to False) OR
(ON_GROUND_VALID is equal to True)
)
Otherwise, set AC_IN_FLIGHT to False.

### FMUREQ-1797: AC_ON_GROUND (Functional)
FMU software shall set AC_ON_GROUND to True if the following evaluates to True:
(
(ON_GROUND is equal to True) OR
(ON_GROUND_VALID is equal to True)
)
Otherwise, set AC_ON_GROUND to False.

### FMUREQ-1801: ISM_FAULT (Functional)
FMU software shall set ISM_FAULT to True if the following logic evaluates to True:
(
(BRAKE_SENSOR_STATUS_VALID is equal to False) OR
(ENGINE_TEMP_VALID_S1 is equal to False) OR
(ENGINE_TEMP_VALID_S2 is equal to False) OR
(FAULT_IGNORE_VALID is equal to False) OR
(CTR_TK_FUEL_LEVEL_VALID is equal to False) OR
(FUEL_TANK_TEMP_VALID is equal to False) OR
(GROUND_SPEED_VALID is equal to False) OR
(ON_GROUND_VALID is equal to False) OR
(PBIT_STATUS_VALID is equal to False) OR
(RECORDED_SPEED_VALID is equal to False)
) is True for greater than ISM_FAULT_CONFIRM_DELAY
Otherwise, set ISM_FAULT to False.

### FMUREQ-1835: FUEL_WING_TK_LEVEL_DIFF (Functional)
FMU Software shall set FUEL_WING_TK_LEVEL_DIFF to (ABS(L_TK_FUEL_LEVEL - R_TK_FUEL_LEVEL)) if the following logic evaluates to True:
(
(L_TK_FUEL_LEVEL_VALID is True) AND
(R_TK_FUEL_LEVEL_VALID is True)
)
Otherwise, maintain the previous value of FUEL_WING_TK_LEVEL_DIFF.

### FMUREQ-1838: FUEL_BALANCE_INHIBIT (Functional)
FMU Software shall set FUEL_BALANCE_INHIBIT to True if the following logic evaluates to True:
(
(L_TK_FUEL_LEVEL_VALID is equal to False) OR
(R_TK_FUEL_LEVEL_VALID is equal to False) OR
([REFUELING] is equal to True) OR
([DEFUELING] is equal to True) OR
(
(AC_ON_GROUND is equal to True) AND
(
(
(ENG1_RUNNING True) AND
(ENG1_RUNNING_VALID True)
) OR
(
(ENG2_RUNNING True) AND
(ENG2_RUNNING_VALID True)
) OR
(
(APU_RUNNING True) AND
(APU_RUNNING_VALID True)
)
)
) OR
(
(XFEED_VALVE_FULLY_CLOSED is equal to False) AND
(XFEED_VALVE_FULLY_CLOSED_VALID is equal to True)
)
)
Otherwise, set FUEL_BALANCE_INHIBIT to False.

### FMUREQ-1840: FUEL_BALANCE_COMPLETE (Functional)
FMU Software shall set FUEL_BALANCE_COMPLETE to True if the following logic evaluates to True:
(
(FUEL_WING_TK_LEVEL_DIFF is less than or equal to FUEL_BALANCE_COMPLETE_TH)
)
Otherwise, set FUEL_BALANCE_COMPLETE to False.

### #89: x_LP_MFLD_LOW_PRESSURE (Container)

#### FMUREQ-1861: L_LP_MFLD_LOW_PRESSURE (Functional)
FMU Software shall set L_LP_MFLD_LOW_PRESSURE to True if the following logic evaluates to True:
(
(L_LP_MFLD_LOW_PRESSURE_RESET is equal to False) AND
(
(L_LP_MFLD_PRESSURE is less than or equal to LP_LOW_PRESSURE_TH) AND
(L_LP_MFLD_PRESSURE_VALID is equal to True)
) is equal to True for greater than LP_LOW_PRESSURE_DELAY
)
Otherwise, maintain the previous value of L_LP_MFLD_LOW_PRESSURE if the following logic evaluates to True:
(
(L_LP_MFLD_LOW_PRESSURE_RESET is equal to False)
)
Otherwise, set L_LP_MFLD_LOW_PRESSURE to False.

#### FMUREQ-1862: L_LP_MFLD_LOW_PRESSURE_RESET (Functional)
FMU Software shall set L_LP_MFLD_LOW_PRESSURE_RESET to True if the following logic evaluates to True:
(
(L_LP_MFLD_PRESSURE is greater than or equal to LP_LOW_PRESSURE_RESET_TH) AND
(L_LP_MFLD_PRESSURE_VALID is equal to True)
) is equal to True for greater than LP_LOW_PRESSURE_DELAY
Otherwise, set L_LP_MFLD_LOW_PRESSURE_RESET to False

#### FMUREQ-1863: R_LP_MFLD_LOW_PRESSURE (Functional)
FMU Software shall set R_LP_MFLD_LOW_PRESSURE to True if the following logic evaluates to True:
(
(R_LP_MFLD_LOW_PRESSURE_RESET is equal to False) AND
(
(R_LP_MFLD_PRESSURE is less than or equal to LP_LOW_PRESSURE_TH) AND
(R_LP_MFLD_PRESSURE_VALID is equal to True)
) is equal to True for greater than LP_LOW_PRESSURE_DELAY
)
Otherwise, maintain the previous value of R_LP_MFLD_LOW_PRESSURE if the following logic evaluates to True:
(
(R_LP_MFLD_LOW_PRESSURE_RESET is equal to False)
)
Otherwise, set R_LP_MFLD_LOW_PRESSURE to False.

#### FMUREQ-1864: R_LP_MFLD_LOW_PRESSURE_RESET (Functional)
FMU Software shall set R_LP_MFLD_LOW_PRESSURE_RESET to True if the following logic evaluates to True:
(
(R_LP_MFLD_PRESSURE is greater than or equal to LP_LOW_PRESSURE_RESET_TH) AND
(R_LP_MFLD_PRESSURE_VALID is equal to True)
) is equal to True for greater than LP_LOW_PRESSURE_DELAY
Otherwise, set R_LP_MFLD_LOW_PRESSURE_RESET to False.

### FMUREQ-1883: AUTO_REFUEL_COMPLETE (Functional)
FMU Software shall set AUTO_REFUEL_COMPLETE to True if the following logic evaluates to True:
(
(FUEL_XFER_MODE is equal to XM_AUTO) AND
(FUEL_XFER_MODE_VALID is equal to True) AND
(DESIRED_FUEL_LEVEL is greater than or equal to FUEL_ON_BOARD) AND
(DESIRED_FUEL_LEVEL_VALID is equal to True) AND
(FUEL_ON_BOARD_VALID is equal to True)
)
Otherwise, set AUTO_REFUEL_COMPLETE to False

## #95: Control Logic (Container)

### #96: Center Tank Pumps Enabled (Container)

#### FMUREQ-1807: CTR_TK_PUMP_1_ENABLE (Functional)
FMU Software shall set CTR_TK_PUMP_1_ENABLE to True if the following logic evaluates to True:
(
(
(CTR_TK_MAN_SWITCH is equal to True) AND
(CTR_TK_MAN_SWITCH_VALID is equal to True) AND
(CTR_TK_PUMP_1_SWITCH is equal to True) AND
(CTR_TK_PUMP_1_SWITCH_VALID is equal to True)
) OR
(
(CTR_TK_MAN_SWITCH is equal to False) AND
(CTR_TK_MAN_SWITCH_VALID is equal to True) AND
(CTR_TK_PUMP_1_AUTO_STOP is equal to False)
)
)
Otherwise, set CTR_TK_PUMP_1_ENABLE to False.

#### FMUREQ-1808: CTR_TK_PUMP_2_ENABLE (Functional)
FMU Software shall set CTR_TK_PUMP_2_ENABLE to True if the following logic evaluates to True:
(
(
(CTR_TK_MAN_SWITCH is equal to True) AND
(CTR_TK_MAN_SWITCH_VALID is equal to True) AND
(CTR_TK_PUMP_2_SWITCH is equal to True) AND
(CTR_TK_PUMP_2_SWITCH_VALID is equal to True)
) OR
(
(CTR_TK_MAN_SWITCH is equal to False) AND
(CTR_TK_MAN_SWITCH_VALID is equal to True) AND
(CTR_TK_PUMP_2_AUTO_STOP is equal to False)
)
)
Otherwise, set CTR_TK_PUMP_2_ENABLE to False.

### #99: Wing Tank Pumps Enabled (Container)

#### FMUREQ-1823: L_TK_PUMP_1_ENABLE (Functional)
FMU Software shall set L_TK_PUMP_1_ENABLE to True if the following logic evaluates to True:
(
(L_TK_PUMP_1_SWITCH is equal to True) AND
(L_TK_PUMP_1_SWITCH_VALID is equal to True)
)
Otherwise, set L_TK_PUMP_1_ENABLE to False.

#### FMUREQ-1824: L_TK_PUMP_2_ENABLE (Functional)
FMU Software shall set L_TK_PUMP_2_ENABLE to True if the following logic evaluates to True:
(
(L_TK_PUMP_2_SWITCH is equal to True) AND
(L_TK_PUMP_2_SWITCH_VALID is equal to True)
)
Otherwise, set L_TK_PUMP_2_ENABLE to False.

#### FMUREQ-1825: R_TK_PUMP_1_ENABLE (Functional)
FMU Software shall set R_TK_PUMP_1_ENABLE to True if the following logic evaluates to True:
(
(R_TK_PUMP_1_SWITCH is equal to True) AND
(R_TK_PUMP_1_SWITCH_VALID is equal to True)
)
Otherwise, set R_TK_PUMP_1_ENABLE to False.

#### FMUREQ-1826: R_TK_PUMP_2_ENABLE (Functional)
FMU Software shall set R_TK_PUMP_2_ENABLE to True if the following logic evaluates to True:
(
(R_TK_PUMP_2_SWITCH is equal to True) AND
(R_TK_PUMP_2_SWITCH_VALID is equal to True)
)
Otherwise, set R_TK_PUMP_2_ENABLE to False.

### #104: CTR_TK_PUMP_x_AUTO_STOP (Container)

#### FMUREQ-1812: CTR_TK_PUMP_1_AUTO_STOP (Functional)
FMU Software shall set CTR_TK_PUMP_1_AUTO_STOP to True if the following logic evaluates to True:
(
(
(FLIGHT_PHASE is equal to FLIGHT_PHASE_TAKEOFF) AND
(FLIGHT_PHASE_VALID is equal to True)
) OR
(
(CTR_TK_LOW_LVL is equal to True) AND
(CTR_TK_LOW_LVL_VALID is equal to True)
) is equal to True for greater than CTR_TK_LO_LVL_DELAY OR
(
(L_TK_LOW_LVL is equal to True) AND
(L_TK_LOW_LVL_VALID is equal to True)
)
)
Otherwise, set CTR_TK_PUMP_1_AUTO_STOP to False.

#### FMUREQ-1813: CTR_TK_PUMP_2_AUTO_STOP (Functional)
FMU Software shall set CTR_TK_PUMP_2_AUTO_STOP to True if the following logic evaluates to True:
(
(
(FLIGHT_PHASE is equal to FLIGHT_PHASE_TAKEOFF) AND
(FLIGHT_PHASE_VALID is equal to True)
) OR
(
(CTR_TK_LOW_LVL is equal to True) AND
(CTR_TK_LOW_LVL_VALID is equal to True)
) is equal to True for greater than CTR_TK_LO_LVL_DELAY OR
(
(R_TK_LOW_LVL is equal to True) AND
(R_TK_LOW_LVL_VALID is equal to True)
)
)
Otherwise, set CTR_TK_PUMP_2_AUTO_STOP to False.

### FMUREQ-1828: XFEED_VALVE_OPEN_CMD (Functional)
FMU Software shall set XFEED_VALVE_OPEN_CMD to True if the following logic evaluates to True:
(
(XFEED_VALVE_SWITCH is equal to True) AND
(XFEED_VALVE_SWITCH_VALID is equal to True) AND
(XFEED_VALVE_FULLY_OPEN is False) AND
(XFEED_VALVE_FULLY_OPEN_VALID is True)
)
Otherwise, set XFEED_VALVE_OPEN_CMD to False.

### FMUREQ-1829: XFEED_VALVE_CLOSE_CMD (Functional)
FMU Software shall set XFEED_VALVE_CLOSE_CMD to True if the following logic evaluates to True:
(
(XFEED_VALVE_SWITCH is equal to False) AND
(XFEED_VALVE_SWITCH_VALID is equal to True) AND
(XFEED_VALVE_FULLY_CLOSED is False) AND
(XFEED_VALVE_FULLY_CLOSED_VALID is True)
)
Otherwise, set XFEED_VALVE_CLOSE_CMD to False.

### #109: FUEL_BALANCE_ENABLE (Container)

#### FMUREQ-1833: FUEL_BALANCE_ENABLE (Functional)
FMU Software shall set FUEL_BALANCE_ENABLE to True if the following logic evaluates to True:
(
(FUEL_BALANCE_ENABLE_RESET is equal to False) AND
(FUEL_BALANCE_PB transitions from False to True) AND
(FUEL_BALANCE_PB_VALID is equal to True) AND
(Previous value of FUEL_BALANCE_ENABLE is equal to False) AND
(FUEL_BALANCE_INHIBIT is equal to False)
)
Otherwise, maintain the previous value of FUEL_BALANCE_ENABLE if the following logic evaluates to True:
(
(FUEL_BALANCE_ENABLE_RESET is equal to False)
)
Otherwise, set FUEL_BALANCE_ENABLE to False.

#### FMUREQ-1834: FUEL_BALANCE_ENABLE_RESET (Functional)
FMU Software shall set FUEL_BALANCE_ENABLE_RESET to True if the following logic evaluates to True:
(
(
(FUEL_BALANCE_PB transitions from False to True) AND
(FUEL_BALANCE_PB_VALID is equal to True) AND
(Previous value of FUEL_BALANCE_ENABLE is equal to True)
) OR
(FUEL_BALANCE_INHIBIT is equal to True) OR
(FUEL_BALANCE_COMPLETE is equal to True for greater than FUEL_BALANCE_COMPLETE_DELAY)
)
Otherwise, set FUEL_BALANCE_ENABLE_RESET to False.

### #112: FUEL_BALANCE_VALVE_x_OPEN_CMD (Container)

#### FMUREQ-1839: FUEL_BALANCE_VALVE_L_OPEN_CMD (Functional)
FMU Software shall set FUEL_BALANCE_VALVE_L_OPEN_CMD to True if the following logic evaluates to True:
(
(FUEL_BALANCE_COMPLETE is equal to False) AND
(FUEL_BALANCE_ENABLE is equal to True) AND
(L_TK_FUEL_LEVEL is greater than R_TK_FUEL_LEVEL) AND
(FUEL_BALANCE_VALVE_R_OPEN is equal to False) AND
(FUEL_BALANCE_VALVE_L_FULLY_OPEN is equal to False) AND
(FUEL_BALANCE_VALVE_L_FULLY_OPEN_VALID is equal to True)
)
Otherwise, set FUEL_BALANCE_VALVE_L_OPEN_CMD to False.

#### FMUREQ-1841: FUEL_BALANCE_VALVE_R_OPEN_CMD (Functional)
FMU Software shall set FUEL_BALANCE_VALVE_R_OPEN_CMD to True if the following logic evaluates to True:
(
(FUEL_BALANCE_COMPLETE is equal to False) AND
(FUEL_BALANCE_ENABLE is equal to True) AND
(R_TK_FUEL_LEVEL is greater than L_TK_FUEL_LEVEL) AND
(FUEL_BALANCE_VALVE_L_OPEN is equal to False)
(FUEL_BALANCE_VALVE_R_FULLY_OPEN is equal to False) AND
(FUEL_BALANCE_VALVE_R_FULLY_OPEN_VALID is equal to True)
)
Otherwise, set FUEL_BALANCE_VALVE_R_OPEN_CMD to False.

### #115: FUEL_BALANCE_VALVE_x_CLOSE_CMD (Container)

#### FMUREQ-1848: FUEL_BALANCE_VALVE_L_CLOSE_CMD (Functional)
FMU Software shall set FUEL_BALANCE_VALVE_L_CLOSE_CMD to True if the following logic evaluates to True:
(
(FUEL_BALANCE_COMPLETE is equal to True) AND
(FUEL_BALANCE_VALVE_L_FULLY_CLOSED is equal to False) AND
(FUEL_BALANCE_VALVE_L_FULLY_CLOSED_VALID is equal to True)
)
Otherwise, set FUEL_BALANCE_VALVE_L_CLOSE_CMD to False.

#### FMUREQ-1849: FUEL_BALANCE_VALVE_R_CLOSE_CMD (Functional)
FMU Software shall set FUEL_BALANCE_VALVE_R_CLOSE_CMD to True if the following logic evaluates to True:
(
(FUEL_BALANCE_COMPLETE is equal to True) AND
(FUEL_BALANCE_VALVE_R_FULLY_CLOSED is equal to False) AND
(FUEL_BALANCE_VALVE_R_FULLY_CLOSED_VALID is equal to True)
)
Otherwise, set FUEL_BALANCE_VALVE_R_CLOSE_CMD to False.

### FMUREQ-1856: APU_LP_VALVE_OPEN_CMD (Functional)
FMU Software shall set APU_LP_VALVE_OPEN_CMD to True if the following logic evaluates to True:
(
(APU_MASTER_SW is equal to True) AND
(APU_MASTER_SW_VALID is equal to True) AND
(APU_FIRE is equal to False) AND
(APU_FIRE_VALID is equal to True) AND
(APU_LP_VALVE_FULLY_OPEN is equal to False) AND
(APU_LP_VALVE_FULLY_OPEN_VALID is equal to True)
)
Otherwise, set APU_LP_VALVE_OPEN_CMD to False.

### FMUREQ-1857: APU_LP_VALVE_CLOSE_CMD (Functional)
FMU Software shall set APU_LP_VALVE_CLOSE_CMD to True if the following logic evaluates to True:
(
(
(
(APU_MASTER_SW is equal to False) AND
(APU_MASTER_SW_VALID is equal to True) AND
) OR
(
(APU_FIRE is equal to True) AND
(APU_FIRE_VALID is equal to True) AND
)
) AND
(APU_LP_VALVE_FULLY_CLOSED is equal to False) AND
(APU_LP_VALVE_FULLY_CLOSED_VALID is equal to True)
)
Otherwise, set APU_LP_VALVE_OPEN_CMD to False.

### FMUREQ-1858: APU_ELEC_PUMP_ENABLE (Functional)
FMU software shall set APU_ELEC_PUMP_ENABLE to True if the following evaluates to True:
(
(APU_MASTER_SW is equal to True) AND
(APU_MASTER_SW_VALID is equal to True) AND
(APU_FIRE is equal to False) AND
(APU_FIRE_VALID is equal to True) AND
(L_LP_MFLD_LOW_PRESSURE is equal to True)
)
Otherwise, set APU_ELEC_PUMP_ENABLE to False.

### #121: x_REFUEL_VALVE_OPEN_CMD (Container)

#### FMUREQ-1877: L_REFUEL_VALVE_OPEN_CMD (Functional)
FMU Software shall set L_REFUEL_VALVE_OPEN_CMD if the following logic evaluates to True:
(
(L_REFUEL_VALVE_CLOSE_CMD is False) AND
(L_REFUEL_VALVE_FULLY_OPEN is False) AND
(L_REFUEL_VALVE_FULLY_OPEN_VALID is True) AND
(L_TK_REFUEL_SW is True) AND
(TK_REFUEL_SW_VALID is True) AND
(FUEL_XFER_MODE_VALID is True) AND
(
(FUEL_XFER_MODE is equal to XM_MAN) OR
(
(FUEL_XFER_MODE is equal to XM_AUTO) AND
(L_TK_HI_LEVEL is equal to False) AND
(L_TK_HI_LEVEL_VALID is equal to True) AND
(AUTO_REFUEL_COMPLETE is equal to False)
)
)
)
Otherwise, set L_REFUEL_VALVE_OPEN_CMD to False.

#### FMUREQ-1879: R_REFUEL_VALVE_OPEN_CMD (Functional)
FMU Software shall set R_REFUEL_VALVE_OPEN_CMD if the following logic evaluates to True:
(
(R_REFUEL_VALVE_CLOSE_CMD is False) AND
(R_REFUEL_VALVE_FULLY_OPEN is False) AND
(R_REFUEL_VALVE_FULLY_OPEN_VALID is True) AND
(R_TK_REFUEL_SW is True) AND
(TK_REFUEL_SW_VALID is True) AND
(FUEL_XFER_MODE_VALID is True) AND
(
(FUEL_XFER_MODE is equal to XM_MAN) OR
(
(FUEL_XFER_MODE is equal to XM_AUTO) AND
(R_TK_HI_LEVEL is equal to False) AND
(R_TK_HI_LEVEL_VALID is equal to True) AND
(AUTO_REFUEL_COMPLETE is equal to False)
)
)
)
Otherwise, set R_REFUEL_VALVE_OPEN_CMD to False.

#### FMUREQ-1881: CTR_REFUEL_VALVE_OPEN_CMD (Functional)
FMU Software shall set CTR_REFUEL_VALVE_OPEN_CMD if the following logic evaluates to True:
(
(CTR_REFUEL_VALVE_CLOSE_CMD is False) AND
(CTR_REFUEL_VALVE_FULLY_OPEN is False) AND
(CTR_REFUEL_VALVE_FULLY_OPEN_VALID is True) AND
(CTR_TK_REFUEL_SW is True) AND
(TK_REFUEL_SW_VALID is True) AND
(FUEL_XFER_MODE_VALID is True) AND
(
(FUEL_XFER_MODE is equal to XM_MAN) OR
(
(FUEL_XFER_MODE is equal to XM_AUTO) AND
(CTR_TK_HI_LEVEL is equal to False) AND
(CTR_TK_HI_LEVEL_VALID is equal to True) AND
(AUTO_REFUEL_COMPLETE is equal to False)
)
)
)
Otherwise, set CTR_REFUEL_VALVE_OPEN_CMD to False.

### #125: x_REFUEL_VALVE_CLOSE_CMD (Container)

#### FMUREQ-1878: L_REFUEL_VALVE_CLOSE_CMD (Functional)
FMU Software shall set L_REFUEL_VALVE_CLOSE_CMD if the following logic evaluates to True:
(
(L_REFUEL_VALVE_FULLY_CLOSED is False) AND
(L_REFUEL_VALVE_FULLY_CLOSED_VALID is True) AND
(
(
(L_TK_REFUEL_SW is False) AND
(TK_REFUEL_SW_VALID is True)
) OR
(
(
(FUEL_XFER_MODE is equal to XM_OFF) OR
(FUEL_XFER_MODE is equal to XM_DEFUEL)
) AND
(FUEL_XFER_MODE_VALID is True)
) OR
(
(FUEL_XFER_MODE is equal to XM_AUTO) AND
(FUEL_XFER_MODE_VALID is True)
(L_TK_HI_LEVEL is equal to True) AND
(L_TK_HI_LEVEL_VALID is equal to True)
) OR
(AUTO_REFUEL_COMPLETE is equal to True)
)
)
Otherwise, set L_REFUEL_VALVE_CLOSE_CMD to False.

#### FMUREQ-1880: R_REFUEL_VALVE_CLOSE_CMD (Functional)
FMU Software shall set R_REFUEL_VALVE_CLOSE_CMD if the following logic evaluates to True:
(
(R_REFUEL_VALVE_FULLY_CLOSED is False) AND
(R_REFUEL_VALVE_FULLY_CLOSED_VALID is True) AND
(
(
(R_TK_REFUEL_SW is False) AND
(TK_REFUEL_SW_VALID is True)
) OR
(
(
(FUEL_XFER_MODE is equal to XM_OFF) OR
(FUEL_XFER_MODE is equal to XM_DEFUEL)
) AND
(FUEL_XFER_MODE_VALID is True)
) OR
(
(FUEL_XFER_MODE is equal to XM_AUTO) AND
(FUEL_XFER_MODE_VALID is True)
(R_TK_HI_LEVEL is equal to True) AND
(R_TK_HI_LEVEL_VALID is equal to True)
) OR
(AUTO_REFUEL_COMPLETE is equal to True)
)
)
Otherwise, set R_REFUEL_VALVE_CLOSE_CMD to False.

#### FMUREQ-1882: CTR_REFUEL_VALVE_CLOSE_CMD (Functional)
FMU Software shall set CTR_REFUEL_VALVE_CLOSE_CMD if the following logic evaluates to True:
(
(CTR_REFUEL_VALVE_FULLY_CLOSED is False) AND
(CTR_REFUEL_VALVE_FULLY_CLOSED_VALID is True) AND
(
(
(CTR_TK_REFUEL_SW is False) AND
(TK_REFUEL_SW_VALID is True)
) OR
(
(
(FUEL_XFER_MODE is equal to XM_OFF) OR
(FUEL_XFER_MODE is equal to XM_DEFUEL)
) AND
(FUEL_XFER_MODE_VALID is True)
) OR
(
(FUEL_XFER_MODE is equal to XM_AUTO) AND
(FUEL_XFER_MODE_VALID is True)
(CTR_TK_HI_LEVEL is equal to True) AND
(CTR_TK_HI_LEVEL_VALID is equal to True)
) OR
(AUTO_REFUEL_COMPLETE is equal to True)
)
)
Otherwise, set CTR_REFUEL_VALVE_CLOSE_CMD to False.

### FMUREQ-1884: DEFUEL_VALVE_OPEN_CMD (Functional)
FMU Software shall set DEFUEL_VALVE_OPEN_CMD to True if the following logic evaluates to True:
(
(FUEL_XFER_MODE is equal to XM_DEFUEL) AND
(FUEL_XFER_MODE_VALID is True) AND
(DEFUEL_VALVE_FULLY_OPEN is equal to False) AND
(DEFUEL_VALVE_FULLY_OPEN_VALID is equal to True)
)
Otherwise, set DEFUEL_VALVE_OPEN_CMD to False.

### FMUREQ-1885: DEFUEL_VALVE_CLOSE_CMD (Functional)
FMU Software shall set DEFUEL_VALVE_CLOSE_CMD to True if the following logic evaluates to True:
(
(FUEL_XFER_MODE is not equal to XM_DEFUEL) AND
(FUEL_XFER_MODE_VALID is True) AND
(DEFUEL_VALVE_FULLY_CLOSED is equal to False) AND
(DEFUEL_VALVE_FULLY_CLOSED_VALID is equal to True)
)
Otherwise, set DEFUEL_VALVE_CLOSE_CMD to False.

### FMUREQ-1800: FUEL_ON_BOARD (Functional)
FMU Software shall set FUEL_ON_BOARD to the value of (L_TK_FUEL_LEVEL + CTR_TK_FUEL_LEVEL+ R_TK_FUEL_LEVEL) and set FUEL_ON_BOARD_VALID to True if the following logic evaluates to True:
(
(L_TK_FUEL_LEVEL_VALID is equal to True) AND
(CTR_TK_FUEL_LEVEL_VALID is equal to True) AND
(R_TK_FUEL_LEVEL_VALID is equal to True) AND
)
Otherwise, set FUEL_ON_BOARD to the value of -1 and set FUEL_ON_BOARD_VALID to False.

## #132: Cockpit Display Logic (Container)

### FMUREQ-1850: FUEL_IMBALANCE_DISPLAY (Functional)
FMU software shall set FUEL_IMBALANCE_DISPLAY to True if the following logic evaluates to True:
(
(FUEL_WING_TK_LEVEL_DIFF is greater than FUEL_IMBALANCE_DISPLAY_TH)
) is equal to True for greater than FUEL_IMBALANCE_DISPLAY_DELAY
Otherwise, set FUEL_IMBALANCE_DISPLAY to False.
